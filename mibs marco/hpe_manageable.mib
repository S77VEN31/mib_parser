SEMI-MIB DEFINITIONS ::= BEGIN


-- -------------------------------------------------------------
-- HPE private manageable MIBs
-- Title:      HPE private manageable MIBs
-- Version:    930
-- Date:       18 Mach 2019
--
-- -------------------------------------------------------------

IMPORTS
	MODULE-IDENTITY, OBJECT-TYPE, enterprises
              FROM SNMPv2-SMI
	nm       FROM HPE-MIB;


hpHttpMgMod MODULE-IDENTITY
    LAST-UPDATED "9706260000Z"
    ORGANIZATION "Hewlett-Packard Web-based Management Working Group" 
    CONTACT-INFO
    "WG E-mail: webmgmt@sysman.hpl.hp.com
         Chair: Brian Harrison
        Postal: Hewlett-Packard
                10500 Ridgeview Court
                Cupertino  CA 95014  USA
           Tel: +1-408-343-5661
           Fax: +1-408-343-6537
        E-mail: brian_harrison@hp.com"
     
    DESCRIPTION
      "Management information for HTTP manageable devices.
       This MIB gives SNMP systems information on how to 
       manage a device using HTTP."
    REVISION     "9706260000Z"
    DESCRIPTION  "Incorporated NetCitizen definitions" 
    REVISION     "9606120000Z"
    DESCRIPTION  "Initial Version"
     
              ::= { hpWebMgmt 1 }

--hp           OBJECT IDENTIFIER ::= { enterprises 11 }
--nm           OBJECT IDENTIFIER ::= { hp 2 }
hpWebMgmt    OBJECT IDENTIFIER ::= { nm 36 }

hpHttpMgObjects       OBJECT IDENTIFIER ::= { hpHttpMgMod 1 }
hpHttpMgNetCitizen    OBJECT IDENTIFIER ::= { hpHttpMgObjects 2 }
-- -------------------------------------------------------------
-- ---------   Textual Conventions    --------------------------
-- -------------------------------------------------------------
Utf8String ::= TEXTUAL-CONVENTION
         DISPLAY-HINT "255a"
         STATUS  current
         DESCRIPTION
              "To facilitate internationalization, this TC
               represents information taken from the ISO/IEC IS 
               10646-1 character set, encoded as an octet string 
               using the UTF-8 character encoding scheme described 
               in RFC 2044 [10].  For strings in 7-bit US-ASCII, 
               there is no impact since the UTF-8 representation is 
               identical to the US-ASCII encoding."
         SYNTAX  OCTET STRING (SIZE (0..255))

-- -------------------------------------------------------------
-- ---------   Scalars    --------------------------------------
-- -------------------------------------------------------------

hpHttpMgVersion	OBJECT-TYPE
    SYNTAX      Utf8String
    MAX-ACCESS  read-only
    STATUS      current
    DESCRIPTION
        "Version number of this entity, e.g. 'A.00.01'. 
		Where several version numbers are available, this represents the software version."
    ::= { hpHttpMgNetCitizen 6 }

hpHttpMgROMVersion	OBJECT-TYPE
    SYNTAX      Utf8String
    MAX-ACCESS  read-only
    STATUS      current
    DESCRIPTION
        "Version number of ROM for this entity, e.g. 'A.00.01'."
    ::= { hpHttpMgNetCitizen 8 }

hpHttpMgSerialNumber	OBJECT-TYPE
    SYNTAX      Utf8String
    MAX-ACCESS  read-only
    STATUS      current
    DESCRIPTION
        "Serial number of entity. 
		It is recommended that this be factory set and read only; 
		if not factory set, should initially be blank."
    ::= { hpHttpMgNetCitizen 9 }

	
END

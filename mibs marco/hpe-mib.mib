HPE-MIB DEFINITIONS ::= BEGIN

-- Title:      HPE
-- Version:    930
-- Date:       23-Jan-2020
--

-- Title:                HPE ROS
--                       Private HPE MIB
-- Version:              7.46
-- Date:                 23 JAN 2020

IMPORTS

    enterprises
                FROM SNMPv2-SMI;

    Percents ::= INTEGER (0..100)
    NetNumber ::=  OCTET STRING (SIZE(4))
    VlanPriority ::= INTEGER (0..7)

nm OBJECT IDENTIFIER ::= { enterprises 11 2 }
nm MODULE-IDENTITY
                LAST-UPDATED "200701020000Z"
                ORGANIZATION "HPE"
                CONTACT-INFO
					"HPE"
                DESCRIPTION
                      "This private MIB module defines HPE private MIBs."
                REVISION "200701020000Z"
                DESCRIPTION
                      "Initial revision."
        ::= { enterprises 11 2 }



-- Some MIB compilers require that the following 7 lines which define the path
-- to nm MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

    
-- At the end of the MIB there is a definition of all RND-specific traps.

rndNotifications OBJECT-IDENTITY
           STATUS      current
           DESCRIPTION " All the nm notifications will reside under this branch
                         as specified in
                         RFC2578 'Structure of Management Information Version 2 (SMIv2)' 8.5"
           ::= { nm 0 }


-- rndMng group contains Management Variables for nm devices

rndMng   OBJECT IDENTIFIER ::= { nm 1  }
-- see hpe-Mng.mib

rndDeviceParams       OBJECT IDENTIFIER ::= { nm 2  }
-- see HPE-DEVICEPARAMS-MIB.MIB

rndBootP       OBJECT IDENTIFIER ::= { nm 24  }
-- see HPE-BOOTP-MIB.MIB

-- ip Specific group  Addition parameters to ip group in MIB-2

ipSpec      OBJECT IDENTIFIER ::= { nm 26 }
-- see rlIp.mib

rsTunning  OBJECT IDENTIFIER ::= { nm 29 }
-- see rlTuning.mib

rndApplications  OBJECT IDENTIFIER ::= { nm 35 }
-- see rlApplication.mib

rsUDP    OBJECT IDENTIFIER ::=  { nm 42}
-- see rlUdp.mib

swInterfaces  OBJECT IDENTIFIER ::= { nm 43 }
-- see rlInterfaces.mib

rlFFT OBJECT IDENTIFIER ::= { nm 47 }

vlan  OBJECT IDENTIFIER ::= { nm 48 }

rlRmonControl   OBJECT IDENTIFIER ::=  { nm 49}
-- see rlRmon.mib

rlBrgMacSwitch       OBJECT IDENTIFIER ::= { nm 50  }
-- see HPE-BRGMACSWITCH-MIB.MIB

rlExperience OBJECT IDENTIFIER ::= { nm 51 }

rlCli OBJECT IDENTIFIER ::= { nm 52 }
--see HPE-CLI-MIB.MIB

-- Used for Drafts not received yet OBJECT IDENTIFIER

rlPhysicalDescription OBJECT IDENTIFIER ::= { nm 53 }

rlIfInterfaces OBJECT IDENTIFIER ::= { nm 54 }
-- see rlInterfaces.mib

rlMacMulticast OBJECT IDENTIFIER ::= { nm 55 }
--see rlbrgmulticast.mib

rlGalileo OBJECT IDENTIFIER ::= { nm 56 }

rlpBridgeMIBObjects OBJECT IDENTIFIER ::= { nm 57 }
--see HPE-BRIDGEMIBOBJECTS-MIB.MIB

rlTelnet OBJECT IDENTIFIER ::= { nm 58 }
--see HPE-TELNET-MIB.MIB

rlPolicy  OBJECT IDENTIFIER ::= { nm 59 }

rlArpSpoofing OBJECT IDENTIFIER ::= { nm 60 }
--see HPE-ARPSPOOFING-MIB.MIB

rlMir  OBJECT IDENTIFIER ::= { nm 61 }
--see HPE-MIR-MIB.MIB

rlIpMRouteStdMIB OBJECT IDENTIFIER ::= { nm 62 }

rl3sw2swTables OBJECT IDENTIFIER ::= { nm 63 }
--see HPE-3SW2SWTABLES-MIB.MIB

rlGvrp  OBJECT IDENTIFIER ::= { nm 64 }
--see HPE-GVRP-MIB.MIB

rlDot3adAgg  OBJECT IDENTIFIER ::= { nm 65 }

rlEmbWeb  OBJECT IDENTIFIER ::= { nm 66 }

rlSwPackageVersion OBJECT IDENTIFIER ::= { nm 67 }
--see HPE-SWPACKAGEVERSION-MIB.MIB

rlBroadcom OBJECT IDENTIFIER ::= { nm 68 }

rlMultiSessionTerminal  OBJECT IDENTIFIER ::= { nm 69 }
--see HPE-MULTISESSIONTERMINAL-MIB.MIB

rlRCli  OBJECT IDENTIFIER ::= { nm 70 }
--see HPE-RCLI-MIB.MIB

rlBgp OBJECT IDENTIFIER ::= { nm 71 }

rlAgentsCapabilitiesGroups  OBJECT IDENTIFIER ::= { nm 72 }

rlAggregateVlan OBJECT IDENTIFIER ::= {nm 73}
--see HPE-AGGREGATEVLAN-MIB.MIB

rlGmrp  OBJECT IDENTIFIER ::= { nm 75 }
--see HPE-GMRP-MIB.MIB

rlDhcpCl OBJECT IDENTIFIER ::= { nm 76 }
--see HPE-DHCPCL-MIB.MIB

------------------------------

rlStormCtrl OBJECT IDENTIFIER ::= { nm 77 }
--see HPE-STORMCTRL-MIB.MIB

rlSsh OBJECT IDENTIFIER ::= { nm 78 }

rlAAA OBJECT IDENTIFIER ::= { nm 79 }

rlRadius  OBJECT IDENTIFIER ::= { nm 80 }
-- see rlAAA.mib

rlTraceRoute  OBJECT IDENTIFIER ::= { nm 81 }
--see HPE-TRACEROUTE-MIB.MIB

rlSyslog  OBJECT IDENTIFIER ::= { nm 82 }

rlEnv  OBJECT IDENTIFIER ::= { nm 83 }
-- rlPhysicalDescription OBJECT IDENTIFIER ::= { rlEnv 1 }
-- entitySensorMIB OBJECT IDENTIFIER ::= { rlEnv 2 }

rlSmon  OBJECT IDENTIFIER ::= { nm 84 }
-- see HPE-SMON-MIB.MIB

rlSocket OBJECT IDENTIFIER ::= { nm 85 }
-- see HPE-SOCKET-MIB.MIB

rlDigitalKeyManage OBJECT IDENTIFIER ::= { nm 86 }
-- see HPE-DIGITALKEYMANAGE-MIB.MIB

rlCopy  OBJECT IDENTIFIER ::= { nm 87 }

rlQosCliMib OBJECT IDENTIFIER ::= { nm 88 }

rlMngInf OBJECT IDENTIFIER ::= { nm 89 }

rlPhy OBJECT IDENTIFIER ::= { nm 90 }

rlJumboFrames OBJECT IDENTIFIER ::= { nm 91 }
-- see HPE-JUMBOFRAMES-MIB.MIB

rlTimeSynchronization OBJECT IDENTIFIER ::= { nm 92 }

rlDnsCl OBJECT IDENTIFIER ::= { nm 93 }

rlCDB  OBJECT IDENTIFIER ::= { nm 94 }
-- see HPE-CDB-MIB.MIB

rldot1x  OBJECT IDENTIFIER ::= { nm 95 }
-- see HPE-DOT1X-MIB.MIB

rlFile  OBJECT IDENTIFIER ::= { nm 96 }

rlAAAEap OBJECT IDENTIFIER ::= { nm 97 }

rlSNMP OBJECT IDENTIFIER ::= { nm 98 }

--rlQosServ OBJECT IDENTIFIER ::= { nm 99 }

rlSsl OBJECT IDENTIFIER ::= { nm 100 }

rlMacBasePrio OBJECT IDENTIFIER ::= { nm 101 }

rlLocalization  OBJECT IDENTIFIER ::= { nm 103 }

rlRs232 OBJECT IDENTIFIER ::= { nm 104 }

rlNicRedundancy OBJECT IDENTIFIER ::= { nm 105 }

rlAmap OBJECT IDENTIFIER ::= { nm 106 }

rlStack OBJECT IDENTIFIER ::= { nm 107 }

rlPoe OBJECT IDENTIFIER ::= { nm 108 }

rlUPnP  OBJECT IDENTIFIER ::= { nm 109 }

rlLldp OBJECT IDENTIFIER ::= { nm 110 }

rlOib OBJECT IDENTIFIER ::= { nm 111 }

rlBridgeSecurity OBJECT IDENTIFIER ::= { nm 112 }

rlDhcpSpoofing  OBJECT IDENTIFIER ::= { nm 113 }

rlBonjour OBJECT IDENTIFIER ::= { nm 114 }

rlLinksysSmartMIB  OBJECT IDENTIFIER ::= { nm 115 }

rlBrgMulticast  OBJECT IDENTIFIER ::= { nm 116 }

rlBrgMcMngr  OBJECT IDENTIFIER ::= { nm 117 }

rlGlobalIpAddrTable OBJECT IDENTIFIER ::= { nm 118 }

dlPrivate OBJECT IDENTIFIER ::= { nm 119 }

rlSecuritySuiteMib OBJECT IDENTIFIER ::= { nm 120 }

rlIntel OBJECT IDENTIFIER ::= { nm 121 }

rlTunnel OBJECT IDENTIFIER ::= { nm 122 }

rlAutoUpdate OBJECT IDENTIFIER ::= { nm 123 }

rlCpuCounters OBJECT IDENTIFIER ::= { nm 124 }

rlLbd  OBJECT IDENTIFIER ::= { nm 127 }

rlErrdisableRecovery  OBJECT IDENTIFIER ::= { nm 128 }

rlIPv6 OBJECT IDENTIFIER ::= { nm 129 }

rlActionAcl  OBJECT IDENTIFIER ::= { nm 130 }

rlSafeGuard OBJECT IDENTIFIER ::= { nm 131 }

rlProtectedPorts OBJECT IDENTIFIER ::= { nm 132}

rlBanner OBJECT IDENTIFIER ::= { nm 133}

rlGreenEth OBJECT IDENTIFIER ::= { nm 134}

rlDlf OBJECT IDENTIFIER ::= { nm 135}

rlVlanTrunking OBJECT IDENTIFIER ::= { nm 136 }

rlTrafficSeg OBJECT IDENTIFIER ::= { nm 138 }

rlImpbFeatures OBJECT IDENTIFIER ::= { nm 139 }

rlStatistics OBJECT IDENTIFIER ::= { nm 141 }

rlDeleteImg  OBJECT IDENTIFIER ::= { nm 142 }

rlCustom1BonjourService OBJECT IDENTIFIER ::= { nm 143 }

rlSpecialBpdu OBJECT IDENTIFIER ::= { nm 144 }

rlTBIMib OBJECT IDENTIFIER ::= { nm 145}

rlWeightedRandomTailDrop OBJECT IDENTIFIER ::= { nm 146}

rlsFlowMib OBJECT IDENTIFIER ::= { nm 147 }

rlPfcMib OBJECT IDENTIFIER ::= { nm 148}

rlEee OBJECT IDENTIFIER ::= { nm 149}

rlEventsMib OBJECT IDENTIFIER ::= { nm 150}

rlPoeBt OBJECT IDENTIFIER ::= { nm 151}

rlWlanMIB OBJECT IDENTIFIER ::= { nm 200 }

rlEtsMib OBJECT IDENTIFIER ::= { nm 201 }

rlQcnMib OBJECT IDENTIFIER ::= { nm 202 }

rlSctMib OBJECT IDENTIFIER ::= { nm 203 }

rlSysmngMib OBJECT IDENTIFIER ::= { nm 204 }

rlFip OBJECT IDENTIFIER ::= { nm 205 }

rlDebugCapabilities OBJECT IDENTIFIER ::= { nm 206 }

rlIpStdAcl  OBJECT IDENTIFIER ::= { nm 207 }

rlSecSd  OBJECT IDENTIFIER ::= { nm 209 }

rlOspf  OBJECT IDENTIFIER ::= { nm 210 }

rlRtRedist OBJECT IDENTIFIER ::= { nm 211 }

rlIpPrefList  OBJECT IDENTIFIER ::= { nm 212 }

rlVoipSnoop  OBJECT IDENTIFIER ::= { nm 213 }

rlDhcpv6  OBJECT IDENTIFIER ::= { nm 214}

rlIpv6Fhs  OBJECT IDENTIFIER ::= { nm 215} 

rlInventoryEnt  OBJECT IDENTIFIER ::= { nm 217}

rlUdld OBJECT IDENTIFIER ::= { nm 218 }

rlSpan OBJECT IDENTIFIER ::= { nm 219 }

rlPortStat OBJECT IDENTIFIER ::= { nm 223 }

rlLan1 OBJECT IDENTIFIER ::= { nm 224 }    

rlIgmp OBJECT IDENTIFIER ::= { nm 225 }

rlRadiusServ OBJECT IDENTIFIER ::= { nm 226 }

rlRouteMap OBJECT IDENTIFIER ::= { nm 227 }

rlPolicyBasedRouting OBJECT IDENTIFIER ::= { nm 228 }

rlSna  OBJECT IDENTIFIER ::= { nm 229 }

rlWBA  OBJECT IDENTIFIER ::= { nm 230 }

rlSLA  OBJECT IDENTIFIER ::= { nm 231 }

rlQosApps OBJECT IDENTIFIER ::= { nm 232 }

rlQueueStatistics OBJECT IDENTIFIER ::= { nm 233 }

rlPNP OBJECT IDENTIFIER ::= { nm 234 }

rlFindit OBJECT IDENTIFIER ::= { nm 235 }

rlCloudManager OBJECT IDENTIFIER ::= { nm 236 }

rlComponentMapper OBJECT IDENTIFIER ::= { nm 243 }

rndEndOfMibGroup   OBJECT IDENTIFIER ::= { nm 1000  }
-- see HPE-ENDOFMIB-MIB.MIB

END
